# coding: utf-8

r"""Examples for a feature class and its view provider."""

import FreeCAD
# import FreeCADGui
from pivy import coin


class Box:
    def __init__(self, obj):
        r"""Add some custom properties to our box feature"""
        obj.addProperty("App::PropertyLength",
                        "Length",
                        "Box",
                        "Length of the box").Length = 1.0
        obj.addProperty("App::PropertyLength",
                        "Width",
                        "Box",
                        "Width of the box").Width = 1.0
        obj.addProperty("App::PropertyLength",
                        "Height",
                        "Box",
                        "Height of the box").Height = 1.0
        obj.Proxy = self
   
    def onChanged(self, fp, prop):
        r"""Do something when a property has changed"""
        FreeCAD.Console.PrintMessage("Change property: " + str(prop) + "\n")
 
    def execute(self, fp):
        r"""Do something when doing a recomputation, this method is mandatory"""
        FreeCAD.Console.PrintMessage("Recompute Python Box feature\n")


class ViewProviderBox:
    def __init__(self, obj):
        r"""Set this object to the proxy object of the actual view provider"""
        obj.addProperty("App::PropertyColor",
                        "Color",
                        "Box",
                        "Color of the box").Color = (1.0, 0.0, 0.0)
        obj.Proxy = self
 
    def attach(self, obj):
        r"""Setup the scene sub-graph of the view provider,
        this method is mandatory
        """
        self.shaded = coin.SoGroup()
        self.wireframe = coin.SoGroup()
        self.scale = coin.SoScale()
        self.color = coin.SoBaseColor()
       
        data = coin.SoCube()
        self.shaded.addChild(self.scale)
        self.shaded.addChild(self.color)
        self.shaded.addChild(data)
        obj.addDisplayMode(self.shaded, "Shaded")
        style = coin.SoDrawStyle()
        style.style = coin.SoDrawStyle.LINES
        self.wireframe.addChild(style)
        self.wireframe.addChild(self.scale)
        self.wireframe.addChild(self.color)
        self.wireframe.addChild(data)
        obj.addDisplayMode(self.wireframe, "Wireframe")
        self.onChanged(obj, "Color")
 
    def updateData(self, fp, prop):
        r"""If a property of the handled feature has changed we have the
        chance to handle this here"""
        # fp is the handled feature,
        # prop is the name of the property that has changed
        l = fp.getPropertyByName("Length")
        w = fp.getPropertyByName("Width")
        h = fp.getPropertyByName("Height")
        self.scale.scaleFactor.setValue(float(l), float(w), float(h))
        pass
 
    def getDisplayModes(self, obj):
        r"""Return a list of display modes."""
        modes = ["Shaded", "Wireframe"]
        return modes
 
    def getDefaultDisplayMode(self):
        r"""Return the name of the default display mode.
        It must be defined in getDisplayModes.
        """
        return "Shaded"
 
    def setDisplayMode(self, mode):
        r"""Map the display mode defined in attach with those defined
        in getDisplayModes.
        Since they have the same names nothing needs to be done.
        This method is optional
        """
        return mode
 
    def onChanged(self, vp, prop):
        r"""Here we can do something when a single property got changed"""
        FreeCAD.Console.PrintMessage("Change property: " + str(prop) + "\n")
        if prop == "Color":
            c = vp.getPropertyByName("Color")
            self.color.rgb.setValue(c[0], c[1], c[2])
 
    def getIcon(self):
        r"""Return the icon in XPM format which will appear in the tree view.
        This method is\ optional and if not defined a default icon is shown.
        """
        return """
            /* XPM */
            static const char * ViewProviderBox_xpm[] = {
            "16 16 6 1",
            "   c None",
            ".  c #141010",
            "+  c #615BD2",
            "@  c #C39D55",
            "#  c #000000",
            "$  c #57C355",
            "        ........",
            "   ......++..+..",
            "   .@@@@.++..++.",
            "   .@@@@.++..++.",
            "   .@@  .++++++.",
            "  ..@@  .++..++.",
            "###@@@@ .++..++.",
            "##$.@@$#.++++++.",
            "#$#$.$$$........",
            "#$$#######      ",
            "#$$#$$$$$#      ",
            "#$$#$$$$$#      ",
            "#$$#$$$$$#      ",
            " #$#$$$$$#      ",
            "  ##$$$$$#      ",
            "   #######      "};
            """
 
    def __getstate__(self):
        r"""When saving the document this object gets stored using
        Python's json module.
        Since we have some un-serializable parts here -- the Coin stuff --
        we must define this method to return a tuple of all serializable objects
        or None
        """
        return None
 
    def __setstate__(self, state):
        r"""When restoring the serialized object from document we have
        the chance to set some internals here.
        Since no data were serialized nothing needs to be done here.
        """
        return None


def makeBox():
    FreeCAD.newDocument()
    a = FreeCAD.ActiveDocument.addObject("App::FeaturePython", "Box")
    Box(a)
    ViewProviderBox(a.ViewObject)


makeBox()
